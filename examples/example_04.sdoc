[DOCUMENT]
TITLE: Example 4: How to include tables

[TEXT]
STATEMENT: >>>
This document shows how to include tables to an SDoc document.
<<<

[REQUIREMENT]
UID: EXAMPLE-4-001
TITLE: Table example
STATEMENT: >>>
.. list-table:: Table Example
   :widths: 25 25 50
   :header-rows: 1

   * - Heading row 1, column 1
     - Heading row 1, column 2
     - Heading row 1, column 3
   * - Row 1, column 1
     -
     - Row 1, column 3
   * - Row 2, column 1
     - Row 2, column 2
     - Row 2, column 3
<<<
