[DOCUMENT]
TITLE: Example 6: How to include MathJax

[TEXT]
STATEMENT: >>>
This document shows how to enable MathJax in SDoc.

The ``--enable-mathjax`` option must be provided as follows:

.. code-block:: text

    strictdoc export . --enable-mathjax --output-dir Output

MathJax in FREETEXT:

.. raw:: latex html

    $$
    \mathbf{\underline{k}}_{\text{a}} =
    \mathbf{\underline{i}}_{\text{a}} \times
    \mathbf{\underline{j}}_{\text{a}}
    $$
<<<

[REQUIREMENT]
UID: EXAMPLE-6-001
TITLE: Requirement #1 title
STATEMENT: >>>
MathJax in requirement's STATEMENT:

.. raw:: latex html

    $$
    \mathbf{\underline{k}}_{\text{a}} =
    \mathbf{\underline{i}}_{\text{a}} \times
    \mathbf{\underline{j}}_{\text{a}}
    $$
<<<
